--- ArubaOS 8.8.0.2_81788
-- vim:set ts=4 sw=4:
WLSX-STATS-MIB DEFINITIONS ::= BEGIN

   IMPORTS
       TEXTUAL-CONVENTION FROM SNMPv2-TC 

       MODULE-IDENTITY,
       OBJECT-TYPE,
       snmpModules,
       Integer32,
       Unsigned32,
	   Counter32,
	   IpAddress,
	   NOTIFICATION-TYPE
           FROM SNMPv2-SMI

       TDomain,
       DisplayString,
       PhysAddress,
       TAddress,
       TimeInterval,
       RowStatus,
       StorageType,
       TestAndIncr,
	   MacAddress,
	   TruthValue
           FROM SNMPv2-TC

       OBJECT-GROUP
           FROM SNMPv2-CONF
		wlsxEnterpriseMibModules
			FROM ARUBA-MIB;

   wlsxStatsMIB MODULE-IDENTITY 
       LAST-UPDATED "202008141745Z"
       ORGANIZATION "Aruba, a Hewlett Packard Enterprise company"
       CONTACT-INFO
            "Postal:    3333 Scott Blvd,
                        Santa Clara, CA 95054
            E-mail:     aruba-ext-eng-reg@hpe.com
            Phone:      408 227 4500
            Fax:        408 752 0626"
       DESCRIPTION
           "This MIB module defines MIB objects which provide
            information about the Statistics in the 
			Aruba controller."
       REVISION        "202008141745Z"
       DESCRIPTION
           "The initial revision."
       ::= { wlsxEnterpriseMibModules 15 }

   wlsxStatsOpGroup     	OBJECT IDENTIFIER ::= { wlsxStatsMIB 1 }

   wlsxStatsRequestTable OBJECT-TYPE
	SYNTAX			SEQUENCE OF WlsxStatsRequestEntry
	MAX-ACCESS		not-accessible
	STATUS			current
	DESCRIPTION
		"
		"
	::= { wlsxStatsOpGroup 1 }

	wlsxStatsRequestEntry OBJECT-TYPE
		SYNTAX WlsxStatsRequestEntry
		MAX-ACCESS not-accessible
		STATUS	current
		DESCRIPTION
			""
		INDEX { wlsxStatsIndex }
		::= { wlsxStatsRequestTable 1 }

	WlsxStatsRequestEntry ::=
		SEQUENCE {
			wlsxStatsIndex	    Integer32,
			wlsxStatsReqType    Integer32,
			wlsxStatsInterval	Integer32,
			wlsxStatsCookie	    DisplayString
		}

	wlsxStatsIndex OBJECT-TYPE
		SYNTAX 	Integer32
		MAX-ACCESS not-accessible
		STATUS	current
		DESCRIPTION
			"
				Stats Index
			"
		::= { wlsxStatsRequestEntry 1 }

	wlsxStatsReqType OBJECT-TYPE
		SYNTAX 	Integer32
		MAX-ACCESS read-write
		STATUS	current
		DESCRIPTION
			"
				Request Type
			"
		::= { wlsxStatsRequestEntry 2 }

	wlsxStatsInterval OBJECT-TYPE
		SYNTAX 	Integer32
		MAX-ACCESS read-write
		STATUS	current
		DESCRIPTION
			"
				Stats Interval
			"
		::= { wlsxStatsRequestEntry 3 }

	wlsxStatsCookie OBJECT-TYPE
		SYNTAX 	DisplayString
		MAX-ACCESS read-write
		STATUS	current
		DESCRIPTION
			"
				Cookie for the config sync operation
			"
		::= { wlsxStatsRequestEntry 4 }

END
